(defun c:page()
  (setvar "cmdecho" 0)
  (vl-load-com)
  (setq acadobj(vlax-get-acad-object))
  (setq doc(vla-get-activedocument acadobj))
  (setq msapce(vla-get-modelspace doc))
  ;(setq page(getint "/n请输入起始页码:"))
  ;(if (= page nil)
    (setq  page 1)
  ; )
;;;  (setq ss(ssget (list(cons 0 "INSERT"))))
;;;  (setq sslen(sslength ss))
 ; (initget "H V S ")(setq GETK (getkword "排序方式:\n [左右上下(H)/左右下上(V)/选择优先(S)]: <H> "))
 ; (princ ">>选择对象...")
 
 (setq GETK H)

 (setq ss(ssget '((-4 . "<and")(0 . "INSERT")(66 . 1)(-4 . "and>"))))
 (setq sslen(sslength ss))
 (setq index0 0 index (sslength ss) sslist '())   
 (repeat index
    (setq sslist (cons (ssname ss index0) sslist))
    (setq index0 (1+ index0))
  )
  ;开始构建图元点位表 ((<图元名: 1d12cb0a950> (10678.2 -367.484 0.0))...)
  (setq index0 0  sslist-ptl '() tmp-pt '())   
  (repeat index
    (setq tmp-pt (cons (nth index0 sslist) (cons (cdr(assoc 10 (entget (nth index0 sslist)))) tmp-pt)))
    (setq sslist-ptl (cons tmp-pt sslist-ptl))
    (setq tmp-pt '())
    (setq index0 (1+ index0))
  )
  ;开始排序
  (cond      
  ;从左到右
  ((or (= GETK "H")(= GETK nil))
    (setq XZ_sortlist 
      (vl-sort sslist-ptl '(lambda (s3 s4) (< (caadr s3) (caadr s4))))
    )
  )
  ; ((or (= GETK "H")(= GETK nil))
  ;   (setq XZ_sortlist (vl-sort
  ;     (vl-sort sslist-ptl '(lambda (s1 s2) (> (cadadr s1) (cadadr s2))))
  ;     '(lambda (s3 s4) (if(equal (cadadr s3) (cadadr s4) 0.6)(< (caadr s3) (caadr s4)))))
  ;   )   
  ; )
  ;从下到上从左到右
  ((= GETK "V")
    (setq XZ_sortlist(reverse sslist-ptl))    
  )
   ;选择顺序
  ((= GETK "S")
    (setq XZ_sortlist  sslist-ptl))
   );cond
  (setq totalpage(+ sslen (- page 1)))
  (setq n 0)
  (repeat sslen
    (setq m 0)
    (setq en(car(nth n XZ_sortlist)))
    (setq xobj(vlax-ename->vla-object en))
    (setq attpage(vla-getattributes xobj))
    (setq svar(vlax-variant-value attpage))
    (setq att_list(vlax-safearray->list svar))
    (setq len(length att_list))
    (repeat len
      (setq pageobj(nth m att_list))
      (setq tag(vla-get-tagstring pageobj))
      (if (= tag "PAGE")
        (vla-put-textstring pageobj (strcat "第 " (itoa page) " 页"))
	    )
      (if(= tag "TOTALPAGE")
        (vla-put-textstring pageobj (strcat "共 " (itoa totalpage) " 页"))
	    )
      (setq m (1+ m))
      )
    (setq n(1+ n))
    (setq page(1+ page))
    )
	(setq topage (1- page))
)
